module example-ops {
    namespace "urn:example-ops:reboot";
    prefix ops;

    revision "2016-07-08" {
        description
          "Initial version.";
        reference
          "example document.";
    }

    container example-ops {
        description
          "Device network config";
        leaf ip {
            type string;
            default "127.0.0.1";
            description
              "Device ip address.";
        }
        leaf port {
            type uint32;
            default 8888;
            description
              "Device MAC address.";
        }
        container groups {
            description
              "NETCONF access control groups.";

            list group {
                key name;

                description
                  "One NACM group entry.  This list will only contain
                   configured entries, not any entries learned from
                   any transport protocols.";

                leaf name {
                    type string;
                    description
                      "Group name associated with this entry.";
                }

                leaf-list user-name {
                    type string;
                    description
                      "Each entry identifies the username of
                       a member of the group associated with
                       this entry.";
                }
            }
        }
    }

    rpc reboot {
        description
          "Reboot operation.";
        input {
            leaf delay {
                type uint32;
                units "seconds";
                default 300;
                description
                  "Delay in seconds.";
            }
            leaf message {
                type string;
                default "message";
                description
                  "Log message.";
            }
        }
    }
}
